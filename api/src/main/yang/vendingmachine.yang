module vendingmachine {
		yang-version 1;
		namespace "urn:opendaylight:params:xml:ns:yang:vendingmachine";
		prefix "vendingmachine";
		organization "Inocybe Technologies";
		contact "Layth Alani <lalani@inocybe.com>";
		description 
			"YANG version of the vendingmachine-MIB.";
		revision "2014-12-10" {
			description "Initial revision of vendingmachine model.";
		}
		
		identity vending-products {
		 	description "different type of products that available in the vending machine.";
		}
		
		identity snacks	{
		base vendingmachine:vending-products;
		description "Different Snacks";	
		}
		
		identity juice {
		base vending-products;
		    description "Beverages water-coca-cola";
		}
		
		identity water {
			base vending-products;
			description "the water bottle option.";
		}
		
		identity sandwich {
			base vending-products;
			description "Sandwich";
		}
		
		typedef DisplayString {
		    type string {
			length "0 .. 255";
			}
		    description
		    	"YANG version of the SMIv2 DisplayString TEXTUAL-CONVENTION.";
		    reference
		    	"RFC 2575, section 2.";
		}
		
		container vendingmachine {
			presence
				"Indicate that the Vending Machine service is available.";
			description
				"Top-level container for all vinding machine database abjects.";
		
		
			leaf vendingmachine-manufacturer {
				type DisplayString;
				config false;
				mandatory true;
				description
				  "this mane of the Vending Machine's manufacturer. Example XXX inc.";
			}
			
			leaf vendingmachine-model-number {
				type DisplayString;
				config false;
				mandatory true;
				description
				  "The name of the vinfing Machine model. Example three products machin.e";
			}
		
			leaf vendingmachine-status {
				type enumeration {
					enum "empty" {
				    	value 0;
				 		 description
				    		"the products are not available.";
					}
					
					enum "availability" {
				    	value 1; 
				  	  description 
				  		  "this indicate that the products is available.";
					}	
				}
				
				config false;
				mandatory true;
				description
				    "this variable indicate the current status of the vanding Machine.";
			}
		
			leaf number-of-products-available {
				type uint32;
				config false;
				default 8;
				description
					"the number of Sandwich, water and juice available.";
			}
		
			leaf number-of-products-leaft {
				type uint32;
				config false;
				description
					"the number of remaining Sandwich, water and juice.";
			}
		}
		rpc make-order{
			description
				"Chose the item that you like to buy. an notification should be send 
				to show thw availibility of that item. error massegae will be return 
				if the item not availablie";
			
			input {
				leaf numberofitems{
					type uint32{
						range "1 .. 10";
					}
					default '1';
					description 
						"This variable controls the number of items that orderd. The order should be 
						1 to 10 items can be bought at one. The default number is 1";
				}
				
				leaf itemtype{
					type identityref {
						base vendingmachine:vending-products;
					}
					default 'water';
					description 
						"This variable descripte the type of products.Vending Machine
						uses this variable to send the proper product";
					
				}
			}
		}
		
		rpc refull-item{
			description 
			"Refull the Vending Machine with the varitouse products.";
			
			input{
				
				leaf quantityofproductprovide {
					type uint32;
					description 
						"the amount of products to re-full.";
					
				}
			}
				
		}
		
		notification vendingmachineOutOfItems{
			description
				"show that the vendingmachine is out of products.";
		}
		
		notification refullvendingmachine{
			description
				"No products.";
			leaf quantityofproduct{
			type uint32;
			description 
				"the amount of products that was re-full.";
			}
			
		}
	
	}
