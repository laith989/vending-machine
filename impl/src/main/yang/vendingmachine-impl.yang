module vendingmachine-impl {
    yang-version 1;
    namespace "urn:opendaylight:params:xml:ns:yang:vendingmachine:impl";
    prefix "vendingmachine-impl";

    import config { prefix config; revision-date 2013-04-05; }
    import opendaylight-md-sal-binding { prefix md-sal-binding; revision-date 2013-10-28;}
	import rpc-context {prefix rpcx; revision-date 2013-06-17; }
    description
        "Service definition for vendingmachine project";

    revision "2014-12-10" {
        description
            "Initial revision";
    }

    identity vendingmachine-impl {
        base config:module-type;
        config:java-name-prefix Vendingmachine;
    }

    augment "/config:modules/config:module/config:configuration" {
        case vendingmachine-impl {
            when "/config:modules/config:module/config:type = 'vendingmachine-impl'";
            container broker {
                uses config:service-ref {
                    refine type {
                        mandatory true;
                        config:required-identity md-sal-binding:binding-broker-osgi-registry;
                    }
                }
            }
            container rpc-registry{
    			uses config:service-ref{
    				refine type {
    					mandatory true;
    					config:required-identity md-sal-binding:binding-rpc-registry;
    				}
    			}
    		}
         }
     }
    augment "/config:modules/config:module/config:state" {
        case vendingmachine-impl {
            when "/config:modules/config:module/config:type = 'vendingmachine-impl'";
        	
            leaf orders-made{
            	type uint32;
            }
            
            rpcx:rpc-context-instance"clear-orders-made-rpc";
        }
    }
    
    identity clear-orders-made-rpc;
    
    rpc clear-orders-made {
    	
    	description
    		"JMX call to clear the orders-made counter.";
    	
    	input {
    		user rpcx:rpc-context-ref{
    			refine context-instance {
    				rpcx:rpc-context-instance clear-orders-made-rpc;
    			}	
    		}
   		}
    }
}
